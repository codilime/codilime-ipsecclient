module sico-ipsec {
    yang-version 1.1;
    namespace urn:ietf:params:xml:ns:yang:sico-ipsec;
    prefix sico-ipsec;

    typedef dotted-quad {
        type string {
            pattern
              '(([0-9]|[1-9][0-9]|1[0-9][0-9]|2[0-4][0-9]|25[0-5])\.){3}'
            + '([0-9]|[1-9][0-9]|1[0-9][0-9]|2[0-4][0-9]|25[0-5])';
        }
        description
          "Four octets written as decimal numbers and
           separated with the '.' (full stop) character.";
    }

    typedef dotted-quad-with-mask {
        type string {
            pattern
              '^(([0-9]|[1-9][0-9]|1[0-9][0-9]|2[0-4][0-9]|25[0-5])\.){3}([0-9]|[1-9][0-9]|1[0-9][0-9]|2[0-4][0-9]|25[0-5])\/([0-9]|1[0-9]|2[0-9]|3[0-2])$';
        }
        description
          "Four octets written as decimal numbers and
           separated with the '.' (full stop) character,
           followed by the slash '/' character and the mask length.";
    }

    typedef authentication-type {
        type string {
            pattern
              'certs|psk';
        }
        description
          "the type of endpoint authentication available within the system";
    }

    typedef monitoring-status {
        type string {
            pattern
              'up|down';
        }
        description
          "the type of tunnel status as seen in monitoring";
    }

    typedef dotted-quad-or-nothing {
        type union {
            type dotted-quad;
            type string {
                pattern '';
            }
        }
    }

    container api {
        list vrf {
            key "client_name";
            leaf id {
                type uint32;
                mandatory "false";
            }
            leaf client_name {
                type string;
                description
                  "name of the vrf as it will appear in the configuration";
            }
            list vlan {
                key "vlan";
                leaf vlan {
                    type uint32;
                    description
                      "vlan number";
                }
                leaf lan_ip {
                    type dotted-quad-with-mask;
                    mandatory "true";
                    description
                      "lan ip with mask for the vlan";
                }
            }
            leaf crypto_ph1 {
                type string;
                mandatory "true";
                description
                  "algorithm names for phase 1 (encryption, hash, dh),
                   separated with a dash '-' character";
            }
            leaf crypto_ph2 {
                type string;
                mandatory "true";
                description
                  "algorithm names for phase 2 (encryption, hash, dh),
                   separated with a dash '-' character";
            }
            leaf physical_interface {
                type string;
                mandatory "true";
                description
                  "the physical interface name for the software virtual interface";
            }
            leaf active {
                type boolean;
                mandatory "true";
                description
                  "a flag whether this vrf is active or is just stored in
                   the database for later";
            }
            leaf ospf {
                type boolean;
                description
                  "a flag whether this vrf has ospf enabled";
            }
            leaf local_as {
                type uint32;
                mandatory "true";
                description
                  "local autonomous system number for the bgp session";
            }
            leaf disable_peer_ips {
                type boolean;
                mandatory "false";
                description
                    "don't use peer IPs and instead route the traffic directly to the interfaces";
            }
            list endpoint {
                key "remote_ip_sec";
                leaf id {
                    type uint32;
                    mandatory "false";
                }
                leaf vrf_id {
                    type uint32;
                    mandatory "false";
                    description
                      "id of the vrf that this endpoint belongs to";
                }
                leaf remote_ip_sec {
                    type dotted-quad;
                    mandatory "true";
                    description
                      "the ip of the remote endpoint that we're connecting to";
                }
                leaf local_ip {
                    type dotted-quad;
                    mandatory "true";
                    description
                      "local ip of the tunnel interface";
                }
                leaf peer_ip {
                    type dotted-quad-or-nothing;
                    mandatory "true";
                    description
                      "peer ip of the tunnel interface";
                }
                leaf remote_as {
                    type uint32;
                    description
                      "autonomous system number of the remote endpoint";
                }
                leaf nat {
                    type boolean;
                    mandatory "true";
                }
                leaf bgp {
                    type boolean;
                    mandatory "true";
                    description
                      "a flag whether a bgp session will attempt to
                       connect on this endpoint";
                }
                leaf source_interface {
                    type string;
                    description
                      "the name of the interface in the hardware that the tunnel
                       will be established on";
                }
                container authentication {
                    leaf type {
                        type authentication-type;
                        mandatory "true";
                        description
                          "type of the authentication for this endpoint, can be
                           either 'certs' or 'psk'.";
                    }
                    leaf psk {
                        type string;
                        description
                          "in case of 'psk' authentication, this holds the password";
                    }
                    leaf local_id {
                        type string;
                        description
                          "in case of 'psk' authentication, this holds the local id";
                    }
                    leaf local_cert {
                        type string;
                        description
                          "in case of 'certs' authentication, this holds the local certificate";
                    }
                    leaf remote_cert {
                        type string;
                        description
                          "in case of 'certs' authentication, this holds the remote certificate";
                    }
                    leaf private_key {
                        type string;
                        description
                          "in case of 'certs' authentication, this holds the private key";
                    }
                    leaf pkcs12_base64 {
                        type string;
                        description
                            "a pkcs12 file containing a certificate, a des3 encrypted key and a CA, encoded in base64";
                    }
                }
            }
        }
        list setting {
            key "name";
            leaf name {
                type string;
            }
            leaf value {
                type string;
                mandatory "true";
            }
        }
        list log {
            config false;
            key "name";
            leaf name {
                type string;
            }
            leaf log {
                type string;
                mandatory "true";
            }
        }
        list error {
            config false;
            leaf id {
                type uint32;
                mandatory "true";
            }
            leaf message {
                type string;
                mandatory "true";
            }
            leaf time {
                type string;
                mandatory "true";
            }
        }
        list monitoring {
            config false;
            key "id";
            leaf id {
                type uint32;
                description "id of the vrf of which the endpoints are requested";
            }
            list endpoint {
                key "id";
                leaf id {
                    type uint32;
                    description "id of the endpoint of which the status is monitored, unique globally";
                }
                leaf local_ip {
                    type dotted-quad;
                }
                leaf peer_ip {
                    type dotted-quad;
                }
                leaf status {
                    type monitoring-status;
                }
            }
        }
        list ca {
            key "id";
            leaf id {
                type uint32;
            }
            leaf ca_file {
                type string;
                mandatory "true";
                description
                  "text contents of the certificate authority file";
            }
        }
        leaf password {
            type string;
        }
    }
}
