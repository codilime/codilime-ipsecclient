/*
 *  Copyright (c) 2021 Cisco and/or its affiliates
 *
 *  This software is licensed under the terms of the Cisco Sample Code License (CSCL)
 *  available here: https://developer.cisco.com/site/license/cisco-sample-code-license/
 */

module ipsecclient {
    yang-version 1.1;
    namespace urn:ietf:params:xml:ns:yang:ipsecclient;
    prefix ipsecclient;

    typedef ipv4-address {
        type string {
            pattern
              '([0-9]|[1-9][0-9]|1[0-9]{2}|2[0-4][0-9]|25[0-5])(\.([0-9]|'
            + '[1-9][0-9]|1[0-9]{2}|2[0-4][0-9]|25[0-5])){3}';
        }
        description
          "An IPv4 address in dotted quad notation using the default
           zone.";
    }

    typedef ipv6-address {
        type string {
            pattern
            // Must support compression through different lengths
            // therefore this regexp is complex.
            '(([0-9a-fA-F]{1,4}:){7}[0-9a-fA-F]{1,4}|'
            + '([0-9a-fA-F]{1,4}:){1,7}:|'
            + '([0-9a-fA-F]{1,4}:){1,6}:[0-9a-fA-F]{1,4}|'
            + '([0-9a-fA-F]{1,4}:){1,5}(:[0-9a-fA-F]{1,4}){1,2}|'
            + '([0-9a-fA-F]{1,4}:){1,4}(:[0-9a-fA-F]{1,4}){1,3}|'
            + '([0-9a-fA-F]{1,4}:){1,3}(:[0-9a-fA-F]{1,4}){1,4}|'
            + '([0-9a-fA-F]{1,4}:){1,2}(:[0-9a-fA-F]{1,4}){1,5}|'
            + '[0-9a-fA-F]{1,4}:((:[0-9a-fA-F]{1,4}){1,6})|'
            + ':((:[0-9a-fA-F]{1,4}){1,7}|:)'
            + ')';
        }
        description
          "An IPv6 address represented as either a full address; shortened
           or mixed-shortened formats, using the default zone.";
    }

    typedef empty-string {
        type string { length "0"; }
        description
          "Empty string.";
    }

    typedef ip-address {
        type union {
            type ipv4-address;
            type ipv6-address;
        }
        description
          "An IPv4 or IPv6 address with no prefix specified.";
    }

    typedef ip-address-or-empty {
        type union {
            type ip-address;
            type empty-string;
        }
        description
          "An IPv4 or IPv6 address with no prefix specified or empty string";
    }

    typedef ipv4-prefix {
        type string {
            pattern
              '([0-9]|[1-9][0-9]|1[0-9]{2}|2[0-4][0-9]|25[0-5])(\.([0-9]|'
            + '[1-9][0-9]|1[0-9]{2}|2[0-4][0-9]|25[0-5])){3}/([0-9]|[12][0-9]|'
            + '3[0-2])';
        }
        description
          "An IPv4 prefix represented in dotted quad notation followed by
           a slash and a CIDR mask (0 <= mask <= 32).";
    }

    typedef ipv6-prefix {
        type string {
            pattern
              '(([0-9a-fA-F]{1,4}:){7}[0-9a-fA-F]{1,4}|'
            + '([0-9a-fA-F]{1,4}:){1,7}:|'
            + '([0-9a-fA-F]{1,4}:){1,6}:[0-9a-fA-F]{1,4}|'
            + '([0-9a-fA-F]{1,4}:){1,5}(:[0-9a-fA-F]{1,4}){1,2}|'
            + '([0-9a-fA-F]{1,4}:){1,4}(:[0-9a-fA-F]{1,4}){1,3}|'
            + '([0-9a-fA-F]{1,4}:){1,3}(:[0-9a-fA-F]{1,4}){1,4}|'
            + '([0-9a-fA-F]{1,4}:){1,2}(:[0-9a-fA-F]{1,4}){1,5}|'
            + '[0-9a-fA-F]{1,4}:((:[0-9a-fA-F]{1,4}){1,6})|'
            + ':((:[0-9a-fA-F]{1,4}){1,7}|:)'
            + ')/(12[0-8]|1[0-1][0-9]|[1-9][0-9]|[0-9])';
        }
        description
          "An IPv6 prefix represented in full, shortened, or mixed
           shortened format followed by a slash and CIDR mask
           (0 <= mask <= 128).";
    }

    typedef ip-prefix {
        type union {
            type ipv4-prefix;
            type ipv6-prefix;
        }
        description
          "An IPv4 or IPv6 prefix.";
    }

    typedef ip-address-mask-optional {
        type union {
            type ipv4-address;
            type ipv6-address;
            type ipv4-prefix;
            type ipv6-prefix;
        }
        description
          "An IPv4 or IPv6 address with optional prefix.";
    }

    typedef authentication-type {
        type string {
            pattern
              'certs|psk';
        }
        description
          "the type of endpoint authentication available within the system";
    }

    typedef monitoring-status {
        type string {
            pattern
              'up|down';
        }
        description
          "the type of tunnel status as seen in monitoring";
    }

    container api {
        list vrf {
            key "client_name";
            leaf id {
                type uint32;
                mandatory "false";
            }
            leaf client_name {
                type string;
                description
                  "name of the vrf as it will appear in the configuration";
            }
            list vlan {
                key "vlan";
                leaf vlan {
                    type uint32;
                    description
                      "vlan number";
                }
                leaf lan_ip {
                    type ip-address-mask-optional;
                    mandatory "true";
                    description
                      "lan ip with mask for the vlan";
                }
            }
            leaf crypto_ph1 {
                type string;
                mandatory "true";
                description
                  "algorithm names for phase 1 (encryption, hash, dh),
                   separated with a dash '-' character";
            }
            leaf crypto_ph2 {
                type string;
                mandatory "true";
                description
                  "algorithm names for phase 2 (encryption, hash, dh),
                   separated with a dash '-' character";
            }
            leaf physical_interface {
                type string;
                mandatory "true";
                description
                  "the physical interface name for the software virtual interface";
            }
            leaf active {
                type boolean;
                mandatory "true";
                description
                  "a flag whether this vrf is active or is just stored in
                   the database for later";
            }
            leaf ospf {
                type boolean;
                description
                  "a flag whether this vrf has ospf enabled";
            }
            leaf local_as {
                type uint32;
                mandatory "true";
                description
                  "local autonomous system number for the bgp session";
            }
            leaf disable_peer_ips {
                type boolean;
                mandatory "false";
                description
                    "don't use peer IPs and instead route the traffic directly to the interfaces";
            }
            list endpoint {
                key "remote_ip_sec";
                leaf id {
                    type uint32;
                    mandatory "false";
                }
                leaf vrf_id {
                    type uint32;
                    mandatory "false";
                    description
                      "id of the vrf that this endpoint belongs to";
                }
                leaf remote_ip_sec {
                    type ipv4-address;
                    mandatory "true";
                    description
                      "the ip of the remote endpoint that we're connecting to";
                }
                leaf local_ip {
                    type ip-address;
                    mandatory "true";
                    description
                      "local ip of the tunnel interface";
                }
                leaf peer_ip {
                    type ip-address-or-empty;
                    mandatory "true";
                    description
                      "peer ip of the tunnel interface";
                }
                leaf remote_as {
                    type uint32;
                    description
                      "autonomous system number of the remote endpoint";
                }
                leaf nat {
                    type boolean;
                    mandatory "true";
                }
                leaf bgp {
                    type boolean;
                    mandatory "true";
                    description
                      "a flag whether a bgp session will attempt to
                       connect on this endpoint";
                }
                leaf source_interface {
                    type string;
                    description
                      "the name of the interface in the hardware that the tunnel
                       will be established on";
                }
                container authentication {
                    leaf type {
                        type authentication-type;
                        mandatory "true";
                        description
                          "type of the authentication for this endpoint, can be
                           either 'certs' or 'psk'.";
                    }
                    leaf psk {
                        type string;
                        description
                          "in case of 'psk' authentication, this holds the password";
                    }
                    leaf local_id {
                        type string;
                        description
                          "in case of 'psk' authentication, this holds the local id";
                    }
                    leaf local_cert {
                        type string;
                        description
                          "in case of 'certs' authentication, this holds the local certificate";
                    }
                    leaf remote_cert {
                        type string;
                        description
                          "in case of 'certs' authentication, this holds the remote certificate";
                    }
                    leaf private_key {
                        type string;
                        description
                          "in case of 'certs' authentication, this holds the private key";
                    }
                    leaf pkcs12_base64 {
                        type string;
                        description
                          "a pkcs12 file containing a certificate, a des3 encrypted key and a CA, encoded in base64";
                    }
                }
            }
        }
        list setting {
            key "name";
            leaf name {
                type string;
            }
            leaf value {
                type string;
                mandatory "true";
            }
        }
        list log {
            config false;
            key "name";
            leaf name {
                type string;
            }
            leaf log {
                type string;
                mandatory "true";
            }
        }
        list source_interface {
            config false;
            leaf name {
                type string;
            }
        }
        container algorithm {
            list phase_1_encryption {
                config false;
                leaf name {
                    type string;
                }
            }
            list phase_1_integrity {
                config false;
                leaf name {
                    type string;
                }
            }
            list phase_1_key_exchange {
                config false;
                leaf name {
                    type string;
                }
            }
            list phase_2_encryption {
                config false;
                leaf name {
                    type string;
                }
            }
            list phase_2_integrity {
                config false;
                leaf name {
                    type string;
                }
            }
            list phase_2_key_exchange {
                config false;
                leaf name {
                    type string;
                }
            }
        }
        list error {
            config false;
            leaf id {
                type uint32;
                mandatory "true";
            }
            leaf message {
                type string;
                mandatory "true";
            }
            leaf time {
                type string;
                mandatory "true";
            }
        }
        list monitoring {
            config false;
            key "id";
            leaf id {
                type uint32;
                description
                  "id of the vrf of which the endpoints are requested";
            }
            list endpoint {
                key "id";
                leaf id {
                    type uint32;
                    description
                      "id of the endpoint of which the status is monitored, unique globally";
                }
                leaf local_ip {
                    type ip-address;
                }
                leaf peer_ip {
                    type ip-address;
                }
                leaf status {
                    type monitoring-status;
                }
            }
        }
        list ca {
            key "id";
            leaf id {
                type uint32;
            }
            leaf ca_file {
                type string;
                mandatory "true";
                description
                  "text contents of the certificate authority file";
            }
        }
        leaf password {
            type string;
        }
        leaf check_switch_basic_auth {
            type boolean;
            description
              "check if setting=switch_password and setting=switch_username are valid";
        }
    }
}
